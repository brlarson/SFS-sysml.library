standard library package Observation {
	doc
	/*
	 * This package models a framework for monitoring Boolean conditions and notifying
	 * registered observers when they change from false to true.
	 */
	 
	private import ScalarValues::Boolean;
	private import Occurrences::Occurrence;
	private import Occurrences::Life;
	private import SequenceFunctions::including;
	private import SequenceFunctions::excluding;
	private import ControlFunctions::select;
	private import ControlPerformances::DecisionPerformance;
	private import ControlPerformances::IfThenPerformance;
//SFS:  removes uses of FeatureReferencingPerformances	
	// private import FeatureReferencingPerformances::FeatureWritePerformance;
	// private import FeatureReferencingPerformances::BooleanEvaluationResultToMonitorPerformance;
	private import Transfers::TransferBefore;
//SFS:
	private import Domain::SetNow;
	private import Domain::GetChangeToTrue;
	private import Performances::BooleanEvaluation;
	private import Transfers::Transfer;

    private struct DefaultMonitorLife[1] :> ChangeMonitor, Life {
        doc
        /*
         * DefaultMonitorLife is the classifier of the singleton Life of the defaultMonitor.
         */
    }
    
	feature defaultMonitor[1] : DefaultMonitorLife {
		doc
		/*
		 * defaultMonitor is a single ChangeMonitor that can be used as a default.
		 */
	}

	struct ChangeSignal {
		doc
		/*
		 * A ChangeSignal is a signal to be sent when the Boolean result of its
		 * changeCondition Expression changes from false to true.
		 */

		bool signalCondition : BooleanEvaluation[1] {
			doc
			/*
			 * A BooleanExpression whose result is being monitored.
			 */
		}
		
		feature signalMonitor : ChangeMonitor {
			doc
			/*
			 * The ChangeMonitor responsible for monitoring the signalCondition.
			 */
		}
	}
	
//SFS: use GetChangeToTrue instead of BooleanEvaluationResultToMonitorPerformance		
	private behavior ObserveChange {
		doc
		/*
		 * Each Performance of ObserveChange waits for the result of the Boolean 
		 * condition of a given ChangeSignal to change from false to true, and, when 
		 * it does, sends the ChangeSignal to a given observer Occurrence.
		 */

		in feature changeObserver : Occurrence[1];
		in feature changeSignal : ChangeSignal[1];
		
		// composite step wait : IfThenPerformance {
		// 	doc
		// 	/*
		// 	 * If the result of the changeSignal.signalCondition is false, then wait for 
		// 	 * it to become true.
		// 	 */

		// 	in bool redefines ifTest {
		// 		not changeSignal.signalCondition()
		// 	}
		// 	in step redefines thenClause : BooleanEvaluationResultToMonitorPerformance {
		// 		in bool onOccurrence = changeSignal.signalCondition;
		// 	}
		// }		
		composite step wait : GetChangeToTrue[1] {
			in feature d = changeObserver {
				feature :>> e = changeSignal.signalCondition as BooleanEvaluation;
			}
		}
		
		succession wait then loadOutgoingBuffer;
//SFS:  need to load outgoing buffer
		step loadOutgoingBuffer : outgoingBuffer.put {
			in value = changeSignal;
		}

		succession loadOutgoingBuffer then transfer;
//SFS:  use Transfer instead of TransferBefore because there's already a succession		
		step transfer : Transfer {
			doc /* move changeSignal as payload to changeObserver */
			end feature :>> source = this;
			end feature :>> target = changeObserver;
		}

		// step transfer : TransferBefore[1] 
		// 	redefines outgoingTransfersFromSelf 
		// 	subsets changeObserver.incomingTransfers {
		// 	doc
		// /*
		// 	* Then send changeSignal to changeObserver.
		// 	*/
			
		// 	end feature source {
		// 		feature redefines sourceOutput = changeSignal;
		// 	}
		// 	end feature target;
		// }
	}
	
//SFS: use SetNow instead of FeatureWritePerformance
	struct ChangeMonitor {
		doc
		/*
		 * A ChangeMonitor is a collection of ongoing ChangeSignal observations 
		 * for various observer Occurrences. It provides convenient operations for 
		 * starting and canceling the observations it manages.
		 */

		private thisMonitor : ChangeMonitor redefines self;
//SFS:  does this need to be a var?		
		private composite feature observations[0..*] : ObserveChange;
		
		// private behavior AssignObservations specializes FeatureWritePerformance {
		// 	doc
		// 	/*
		// 	 * Assign a replacement set of observations as those being managed by a
		// 	 * given ChangeMonitor.
		// 	 */

		// 	in feature monitor : ChangeMonitor redefines onOccurrence {
		// 		feature redefines startingAt {
		// 			feature redefines accessedFeature, observations;
		// 		}
		// 	}
		// 	inout feature redefines replacementValues[0..*] : ObserveChange;
		// }
		
		private behavior AssignObservations specializes SetNow {
			in feature monitor : ChangeMonitor redefines d {
				feature observations redefines f;
			}
			in feature replacementValues : ObserveChange redefines v;
		}	

//SFS:  make replacementValues 'in'		
		step startObservation { 
			doc
			/*
			 * Start an observation of a given ChangeSignal for a given Occurrence.
			 */

			in observer : Occurrence[1]; 
			in signal : ChangeSignal[1];
			private composite step observation : ObserveChange {
				in changeObserver = observer;
				in changeSignal = signal;
			}
			private composite step addObservation : AssignObservations[1] {
				in monitor = thisMonitor; 
				// inout
				in replacementValues = observations->including(observation);	
			}
		}
		
//SFS:  make replacementValues 'in'		
		step cancelObservation { 
			doc
			/*
			 * Cancel all observations of a given ChangeSignal for a given Occurrence. 
			 */

			in observer : Occurrence[1]; 
			in signal : ChangeSignal[1];
			private feature observations[0..*] : ObserveChange = 
				observations->select{in observation : ObserveChange; 
					observation.changeObserver == observer and observation.changeSignal == signal
				};
			private composite step removeObservation : AssignObservations[1] {
				in monitor = thisMonitor; 
				// inout
				in replacementValues = observations->excluding(observations);
			}
		}
	}	
}
