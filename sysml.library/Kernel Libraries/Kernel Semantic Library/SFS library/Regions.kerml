library package Regions {
    doc
    /*
    *  SFS:  Metaphysical
    * A region is a contiguous, three-dimensional volume at a particular place in a particular frame-of-reference.
    * The location of a thing is the region it occupies (within a frame-of-reference, at a particular moment of time).
    * The surface of a region is its boundary.
    */
    private import SpatialFrames::SpatialFrame;
    private import Occurrences::Occurrence;
	private import Assertion::Assert;
    private import Performances::BooleanEvaluation;
    private import Clocks::Clock;
    private import Clocks::universalClock;
    private import Tangibility::Virtual;
    private import Tangibility::Physical;
    private import SequenceFunctions::notEmpty;

    type FrameOfReference specializes Base::Anything {
        doc
        /*
        * SFS:  A frame of reference serves as the reference for the location of an occurrence.
        * All inertial frames-of-reference are completely equivalent for the formulation of the 
        * Laws of Physics. (relativity)
        * A frame of reference has an existence independent of objects and processes occurring
        * within it. (substantialism)
        * Within a frame of reference, time progresses uniformly, and simultenaity is
        * well-defined. (Newtonian spacetime)
        */
        feature clock : Clock default universalClock;
    }

    feature universalFrameOfReference : FrameOfReference {
        doc
        /*
        * SFS: universalFrameOfReference is a fixed frame of reference used as a
        * universal default.
        */
        feature :>> clock = universalClock;
    }

    type Region specializes Base::Anything {
        doc
        /*
        * SFS:  A region is a contiguous, three-dimensional volume at a particular
        * place in a particular frame-of-reference. [9]
        * Regions do not have parts.
        * A region may overlap or contain other regions.
        */
        feature frameOfReference : FrameOfReference default universalFrameOfReference;
    }

    type Point specializes Base::Anything {
        doc
        /*
        *  SFS:  Point is a metaphysical 0-dimensional entity.
        */
        feature frameOfReference : FrameOfReference default universalFrameOfReference;
    }

    type Surface specializes Base::Anything {
        doc
        /*
        *  SFS:  Surface is the set of points at the boundary of a Region.
        */
        feature frameOfReference : FrameOfReference default universalFrameOfReference;
    }
 
    /**
     * Represents a spatial location or position within a system.
     * This function can be used to define or reference points, areas, or regions
     * in a model where specific coordinates or spatial context is needed.
     */
    function Location {
        doc
        /*
        * SFS:  The location function relates spatial occurrences to their region.
        * This is the "L" exact location primitive. 
        * Uses o.frameOfReference as the frame-of-reference for the region.
        */
//SFS:  Assert.lean gets confused with the "L" notation
//        @Assert{n="Location"; f="<< Location : o~Occurrence := result~Region | o L result >>";}
        inv { o.isClosed and o.innerSpaceDimension == 3 and o.outerSpaceDimension == 3
            and o.frameOfReference == (result as Region).frameOfReference 
            }
        in o : Occurrence;
        return result : Region;
        if o istype Physical ? (o as Physical).location 
          else if o istype Virtual and notEmpty((o as Virtual).allocatedTo) ? Location((o as Virtual).allocatedTo)
            else if o istype Virtual and notEmpty((o as Virtual).delegatedTo) ? Location((o as Virtual).delegatedTo)
                else Regions::noWhere
   }

     // SFS:  Two things having the same location are the same thing (df-lfu)
    @Assert{n="locational functionality"; 
        f="<< LFU : : forall x~Occurrence forall r1,r2~Region are"+
          " ( (Location(x)=r1 and Location(x)=r2) implies r1=r2 ) >>"; t="lfu";}

    // SFS:  No two things share an exact location.
    @Assert{n="injectivity of location"; 
        f="<< LIN : : forall x,y~Occurrence forall r~Region are"+
          " ( (Location(x)=r and Location(y)=r) implies x=y ) >>"; t="lin";}


    predicate PointInRegion {
        doc /* SFS: Point is contained in Region; "in" is a set mebership relation */
        @Assert{n="PointInRegion"; f="<< PointInRegion : point~Point, region~Region : "+
                " point in region >>";}
        in point : Point;
        in region : Region;
        inv { point.frameOfReference == region.frameOfReference }
    }

    predicate PointOnSurface {
        doc /* SFS: Point is on a Surface */
        @Assert{n="PointOnSurface"; f="<< PointOnSurface : point~Point, surface~Surface : "+
                " point in surface >>";}
        in point : Point;
        in surface : Surface;
        inv { point.frameOfReference == surface.frameOfReference }
    }

    predicate RegionOverlap {
        doc /* SFS:  Two regions containing the same point overlap. 
            * This is the "O" relation (df-rov).
            * Regions are disjoint if they don't overlap */
        @Assert{n="RegionOverlap"; f="<< RegionOverlap : r1~Region, r2~Region :"+
                "exists p~Point that (PointInRegion(p,r1) and PointInRegion(p,r2)) >>"; t="RegionOverlap";}
        in r1 : Region;
        in r2 : Region;
        inv { r1.frameOfReference == r2.frameOfReference }
    }


    predicate RegionContainment {
        doc /* SFS:  A region contains another, when it contains all of its points.
            *  true when r1 contains r2 
            * This is the "C" relation (df-rco). */
        @Assert{n="RegionContainment"; f="<< RegionContainment : r1~Region, r2~Region :"+
                "forall p~Point are (PointInRegion(p,r2) implies PointInRegion(p,r1)) >>"; t="RegionContainment";}
        in r1 : Region;
        in r2 : Region;
        inv { r1.frameOfReference == r2.frameOfReference }
    }

    doc /* SFS: Regions overlap only if one contains the other. This property is called no interpenetration. */
    @Assert{n="NOINTP"; f="<< NOINTP : : forall r1,r2~Region are "+
            "RegionOverlap(r1,r2) implies (RegionContainment(r1,r2) or RegionContainment(r2,r1)) >>"; t="no_interpenetration";}

    doc /* SFS: Parthood implies regional containment. This property is called expansivity. */
    @Assert{n="EXPNS"; f="<< EXPNS : : forall x,y~Occurrence forall r1,r2~Region are "+
           "( (Location(x)=r1 and Location(y)=r2 and PartOf(x,y)) implies RegionContainment(r2,r1) ) >>"; t="expansivity";}

    predicate AtomicRegion {
        doc /* SFS:  A region is atomic, Ar , when it contains no other regions (in the location relation).
         * This is the "A" operator (df-rat). */
        @Assert{n="AtomicRegion"; f="<< AtomicRegion : r~Region : "+
                "forall r1~Region are ( RegionContainment(r,r1) implies r = r1 ) >>"; t="AtomicRegion";}
        in r : Region;
    }

    // Atomic regions are disjoint (df-rdi)
    @Assert{n="AtomicRegionDisjoint"; f="<< AtomicRegionDisjoint : :"+ 
        "forall r1,r2~Region are "+
        "   ( (AtomicRegion(r1) and AtomicRegion(r2)) implies "+
        "     (not RegionOverlap(r1,r2) or r1=r2) ) >>"; t="rdi";}

    // Atomic parts have atomic regions
    @Assert{n="APAR"; f="<< APAR : : forall x~Occurrence forall r~Region are "+
            "(Location(x)=r and AtomicPart(x)) implies AtomicRegion(r) >>"; t="apar";}
 
    abstract predicate Adjacent specializes BooleanEvaluation {
        doc /* SFS: Adjacent is the infinitesimal-closeness relation p1Ap2 --
          * p1 and p2 are infinitesimally close points. This is the "Adj" set
          * used informally below (df-adjp): p2 in Adj(p) reads Adjacent(p,p2). */
        @Assert{n="Adjacent"; f="<< Adjacent : p1~Point, p2~Point : p1Ap2 >>";}
        in p1 : Point;
        in p2 : Point;
    }

    function RegionSurface {
        doc /* SFS: The surface of a region is all the points on its boundary */
        @Assert{n="RegionSurface"; f="<< RegionSurface : r~Region := result~Surface | "+
                "forall p~Point are (PointOnSurface(p,result) iff (PointInRegion(p,r) and "+
                "  exists p2~Point that ( Adjacent(p,p2) and not PointInRegion(p2,r) ))) >>"; t="RegionSurface";}
        in r : Region;
        return result : Surface;
        inv { r.frameOfReference == (result as Surface).frameOfReference}
    }

    function RegionInterior {
        doc /* SFS:  The interior of a region includes all the points in a region
          * not on its surface */
        @Assert{n="RegionInterior"; f="<< RegionInterior : r~Region := result~Region | "+
            "forall p~Point are (PointInRegion(p,result) iff "+
            "  (PointInRegion(p,r) and not PointOnSurface(p,RegionSurface(r))) ) >>"; t="RegionInterior";}
        in r : Region;
        return result : Region;
        inv { r.frameOfReference == (result as Region).frameOfReference}
    }

    function RegionFilm {
        doc /* SFS: The film of a region is a surface of which it's the interior */
        @Assert{n="RegionFilm"; f="<< RegionFilm : r~Region := result~Surface | "+
            " forall p~Point are ( PointOnSurface(p,result) iff "+
            " (not PointInRegion(p,r) and exists p2~Point that "+
            "    (PointOnSurface(p2,RegionSurface(r)) and Adjacent(p,p2)))) >>"; t="RegionFilm";}
        in r : Region;
        return result : Surface;
        inv { r.frameOfReference == (result as Surface).frameOfReference}
    }

    predicate ExternallyConnected {
        doc /* SFS:  This is the externally connected (EC) relation  of Region Connection Calculus
          * r1 and r2 don't overlap, but some point on the film of r1 is in r2 */
        @Assert{n="ExternallyConnected"; f="<< ExternallyConnected : r1~Region, r2~Region : "+
            " not RegionOverlap(r1,r2) and exists p~Point that ( PointOnSurface(p,RegionFilm(r1)) and PointInRegion(p,r2) ) >>"; t="ExternallyConnected";}
        in r1 : Region;
        in r2 : Region;
        inv { r1.frameOfReference == r2.frameOfReference }
    }

    predicate FilmConnected {
        doc /* SFS:  This is needed for Occurrences::JustOutsideOf. */
        @Assert{n="FilmConnected"; f="<< FilmConnected : r1~Region, r2~Region :"+
          " exists p~Point that ( PointOnSurface(p,RegionFilm(r1)) and PointOnSurface(p,RegionFilm(r2)) ) >>";}
        in r1 : Region;
        in r2 : Region;
        inv { r1.frameOfReference == r2.frameOfReference }
    }

    feature noWhere : Region {
        /* things which have no location are no where */
    }
   
}
